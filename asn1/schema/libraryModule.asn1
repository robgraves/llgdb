LibraryModule DEFINITIONS AUTOMATIC TAGS ::= 
BEGIN
	BoardGames ::= SEQUENCE OF BoardGame

	BoardGame ::= SEQUENCE       
	{
		id			INTEGER DEFAULT NULL,                      
     	name      	OCTET STRING (SIZE(1..60)) DEFAULT NULL,
     	desc		OCTET STRING (SIZE(1..255)) DEFAULT NULL, 
		min-players	INTEGER DEFAULT NULL,
		max-players	INTEGER DEFAULT NULL 
  	}                                                     
END
